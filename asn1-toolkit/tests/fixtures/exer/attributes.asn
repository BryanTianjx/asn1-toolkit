AttrTest DEFINITIONS ::= BEGIN
Record ::= SEQUENCE {
  flag [ATTRIBUTE] BOOLEAN,
  count [ATTRIBUTE] INTEGER (-100..100),
  big [ATTRIBUTE] INTEGER,
  opt [ATTRIBUTE] INTEGER (0..10) OPTIONAL,
  mode [ATTRIBUTE] INTEGER (0..10) DEFAULT 3,
  minimum [ATTRIBUTE] INTEGER (-9223372036854775808..9223372036854775807) DEFAULT -9223372036854775808
}
END
