Entries DEFINITIONS XER INSTRUCTIONS AUTOMATIC TAGS ::= BEGIN
  Record ::= SEQUENCE { count INTEGER (0..255), enabled [ATTRIBUTE] BOOLEAN, text UTF8String }
  ENCODING-CONTROL JER
    [ARRAY] SEQUENCE
END
